PM-File-Description-MSC

DEFINITIONS AUTOMATIC TAGS ::=

BEGIN

MeasDataCollection::=SEQUENCE {
measFileHeader MeasFileHeader,
measData SEQUENCE OF MeasData,
measFileFooter MeasFileFooter}

MeasFileHeader::=SEQUENCE{
fileFormatVersion INTEGER,
senderName UTF8String (SIZE(0..400)),
senderType SenderType,
vendorName PrintableString (SIZE (0..32)),
collectionBeginTime TimeStamp}

SenderType::=PrintableString (SIZE (0..8))

TimeStamp::=GeneralizedTime

MeasData::=SEQUENCE {
nEId NEId,
measInfo SEQUENCE OF MeasInfo}

NEId::=SEQUENCE{
nEUserName PrintableString(SIZE(0..64)),
nEDistinguishedName PrintableString (SIZE (0..400))}

MeasInfo::=SEQUENCE {
measStartTime TimeStamp,
granularityPeriod INTEGER,
measTypes SEQUENCE OF MeasType,
measValues SEQUENCE OF MeasValue}

MeasType::=PrintableString (SIZE (1..32))

MeasValue::=SEQUENCE {
measObjInstId MeasObjInstId,
measResults SEQUENCE OF MeasResult,
suspectFlag BOOLEAN DEFAULT FALSE}

MeasObjInstId::=PrintableString (SIZE (1..64))

MeasResult::=CHOICE {
iValue INTEGER (0..4294967295),
rValue REAL,
noValue NULL}

MeasFileFooter::=TimeStamp
END
